------------------------------------------------------------
-- EMERSON NETWORK POWER
-- RDU-SIC G2 Device MIB. 
-- Using Generate Template V1.0
-- Copyright 2008-2015 Emerson Corporation.
-- All rights reserved.
------------------------------------------------------------

ENP_AC_CRV+-MIB DEFINITIONS ::= BEGIN

IMPORTS
	MODULE-IDENTITY, OBJECT-TYPE, NOTIFICATION-TYPE,Integer32, Counter32, enterprises	
		FROM SNMPv2-SMI
	TEXTUAL-CONVENTION, DisplayString, DateAndTime
		FROM SNMPv2-TC;
	
------------------------------------------------------------
-- Node definitions
------------------------------------------------------------
enp OBJECT IDENTIFIER ::= { enterprises 13400 }
	
products OBJECT IDENTIFIER ::= { enp 2 }

ENP_AC_CRV+ MODULE-IDENTITY
	LAST-UPDATED "201309020955Z"
	ORGANIZATION "EMERSON NETWORK POWER (ENPC)"
	CONTACT-INFO "EMERSON NETWORK POWER"
	REVISION     "200"
	DESCRIPTION  "EMERSON NETWORK POWER (ENPC) For RDU-SIC G2 MIB."
	::= { products 339 }

------------------------------------------------------------
-- Textual conventions
------------------------------------------------------------

AlarmSeverity ::= TEXTUAL-CONVENTION
	STATUS current
	DESCRIPTION "
		The severity of the alarm. One of
		(1) informational
		(2) warning
		(3) critical"
	SYNTAX INTEGER {
		informational(1),
		warning(2),
		critical(3) }
		
AlarmStatusChange ::= TEXTUAL-CONVENTION
	STATUS current
	DESCRIPTION "
		Indicates 'activated' (0) or 'deactivated' (1) alarm events."
	SYNTAX INTEGER {
		activated(0),
		deactivated(1) }

------------------------------------------------------------
-- 1.1 Identification of the device { ENP_AC_CRV+ 1 }
------------------------------------------------------------

ident OBJECT IDENTIFIER ::= { ENP_AC_CRV+ 1 }
															
identManufacturer OBJECT-TYPE
	SYNTAX DisplayString
	MAX-ACCESS read-only
	STATUS current
	DESCRIPTION "
		The name of the device manufacturer."
	::= { ident 1 }

identModel OBJECT-TYPE
	SYNTAX DisplayString
	MAX-ACCESS read-only
	STATUS current
	DESCRIPTION "
		The manufacturers model designation of the device."
	::= { ident 2 }
	
identIndex OBJECT-TYPE
	SYNTAX Integer32
	MAX-ACCESS read-write
	STATUS current
	DESCRIPTION "
		The sequence number of the device."
	::= { ident 3 }

------------------------------------------------------------
-- 1.2 system values { ENP_AC_CRV+ 2 }
------------------------------------------------------------
system OBJECT IDENTIFIER ::= { ENP_AC_CRV+ 2 }
	
		
		

------------------------------------------------------------
--gourp2
------------------------------------------------------------
group2 OBJECT IDENTIFIER ::= { system 2 }
softshutdownstatus OBJECT-TYPE
		SYNTAX INTEGER {
			no(0),
			yes(1)
 }
		MAX-ACCESS read-only
		STATUS current
		DESCRIPTION
		"softshutdownstatus, status."
		::= { group2 2}
paneloff OBJECT-TYPE
		SYNTAX INTEGER {
			no(0),
			yes(1)
 }
		MAX-ACCESS read-only
		STATUS current
		DESCRIPTION
		"paneloff, status."
		::= { group2 3}
monitorshutdown OBJECT-TYPE
		SYNTAX INTEGER {
			no(0),
			yes(1)
 }
		MAX-ACCESS read-only
		STATUS current
		DESCRIPTION
		"monitorshutdown, status."
		::= { group2 4}
refrigeration OBJECT-TYPE
		SYNTAX INTEGER {
			no(0),
			yes(1)
 }
		MAX-ACCESS read-only
		STATUS current
		DESCRIPTION
		"refrigeration, status."
		::= { group2 5}
heatingflag OBJECT-TYPE
		SYNTAX INTEGER {
			no(0),
			yes(1)
 }
		MAX-ACCESS read-only
		STATUS current
		DESCRIPTION
		"heatingflag, status."
		::= { group2 6}
humidification OBJECT-TYPE
		SYNTAX INTEGER {
			no(0),
			yes(1)
 }
		MAX-ACCESS read-only
		STATUS current
		DESCRIPTION
		"humidification, status."
		::= { group2 7}
dehumidifying OBJECT-TYPE
		SYNTAX INTEGER {
			no(0),
			yes(1)
 }
		MAX-ACCESS read-only
		STATUS current
		DESCRIPTION
		"dehumidifying, status."
		::= { group2 8}
fan1status OBJECT-TYPE
		SYNTAX INTEGER {
			normal(0),
			fault(1)
 }
		MAX-ACCESS read-only
		STATUS current
		DESCRIPTION
		"fan1status, status."
		::= { group2 9}
fan2status OBJECT-TYPE
		SYNTAX INTEGER {
			normal(0),
			fault(1)
 }
		MAX-ACCESS read-only
		STATUS current
		DESCRIPTION
		"fan2status, status."
		::= { group2 10}
fan3status OBJECT-TYPE
		SYNTAX INTEGER {
			normal(0),
			fault(1)
 }
		MAX-ACCESS read-only
		STATUS current
		DESCRIPTION
		"fan3status, status."
		::= { group2 11}
fan4status OBJECT-TYPE
		SYNTAX INTEGER {
			normal(0),
			fault(1)
 }
		MAX-ACCESS read-only
		STATUS current
		DESCRIPTION
		"fan4status, status."
		::= { group2 12}
condensatepumpoutput OBJECT-TYPE
		SYNTAX INTEGER {
			outputclose(0),
			outputenable(1)
 }
		MAX-ACCESS read-only
		STATUS current
		DESCRIPTION
		"condensatepumpoutput, status."
		::= { group2 13}
compressoroutput OBJECT-TYPE
		SYNTAX INTEGER {
			outputclose(0),
			outputenable(1)
 }
		MAX-ACCESS read-only
		STATUS current
		DESCRIPTION
		"compressoroutput, status."
		::= { group2 14}
electricheatingoutput OBJECT-TYPE
		SYNTAX INTEGER {
			outputclose(0),
			outputenable(1)
 }
		MAX-ACCESS read-only
		STATUS current
		DESCRIPTION
		"electricheatingoutput, status."
		::= { group2 15}
fanoutput OBJECT-TYPE
		SYNTAX INTEGER {
			outputenable(0),
			outputclose(1)
 }
		MAX-ACCESS read-only
		STATUS current
		DESCRIPTION
		"fanoutput, status."
		::= { group2 16}
humidifieroutput OBJECT-TYPE
		SYNTAX INTEGER {
			outputclose(0),
			outputenable(1)
 }
		MAX-ACCESS read-only
		STATUS current
		DESCRIPTION
		"humidifieroutput, status."
		::= { group2 17}
commonalarmoutput OBJECT-TYPE
		SYNTAX INTEGER {
			outputclose(0),
			outputenable(1)
 }
		MAX-ACCESS read-only
		STATUS current
		DESCRIPTION
		"commonalarmoutput, status."
		::= { group2 18}
liquidsolenoidvalveoutput OBJECT-TYPE
		SYNTAX INTEGER {
			outputclose(0),
			outputenable(1)
 }
		MAX-ACCESS read-only
		STATUS current
		DESCRIPTION
		"liquidsolenoidvalveoutput, status."
		::= { group2 19}
highpressurealarm OBJECT-TYPE
		SYNTAX INTEGER {
			normal(0),
			alarm(1)
 }
		MAX-ACCESS read-only
		STATUS current
		DESCRIPTION
		"highpressurealarm, status."
		::= { group2 20}
lowpressurealarm OBJECT-TYPE
		SYNTAX INTEGER {
			normal(0),
			alarm(1)
 }
		MAX-ACCESS read-only
		STATUS current
		DESCRIPTION
		"lowpressurealarm, status."
		::= { group2 21}
abnormalhighpressurealarm OBJECT-TYPE
		SYNTAX INTEGER {
			normal(0),
			alarm(1)
 }
		MAX-ACCESS read-only
		STATUS current
		DESCRIPTION
		"abnormalhighpressurealarm, status."
		::= { group2 22}
exhausttemperaturealarm OBJECT-TYPE
		SYNTAX INTEGER {
			normal(0),
			alarm(1)
 }
		MAX-ACCESS read-only
		STATUS current
		DESCRIPTION
		"exhausttemperaturealarm, status."
		::= { group2 23}
exhaustlowsuperheat OBJECT-TYPE
		SYNTAX INTEGER {
			normal(0),
			alarm(1)
 }
		MAX-ACCESS read-only
		STATUS current
		DESCRIPTION
		"exhaustlowsuperheat, status."
		::= { group2 24}
returnairhightempalarm OBJECT-TYPE
		SYNTAX INTEGER {
			normal(0),
			alarm(1)
 }
		MAX-ACCESS read-only
		STATUS current
		DESCRIPTION
		"returnairhightempalarm, status."
		::= { group2 25}
supplyairlowtempalarm OBJECT-TYPE
		SYNTAX INTEGER {
			normal(0),
			alarm(1)
 }
		MAX-ACCESS read-only
		STATUS current
		DESCRIPTION
		"supplyairlowtempalarm, status."
		::= { group2 26}
supplyairhightempalarm OBJECT-TYPE
		SYNTAX INTEGER {
			normal(0),
			alarm(1)
 }
		MAX-ACCESS read-only
		STATUS current
		DESCRIPTION
		"supplyairhightempalarm, status."
		::= { group2 27}
returnairhighhumalarm OBJECT-TYPE
		SYNTAX INTEGER {
			normal(0),
			alarm(1)
 }
		MAX-ACCESS read-only
		STATUS current
		DESCRIPTION
		"returnairhighhumalarm, status."
		::= { group2 28}
returnairlowhumalarm OBJECT-TYPE
		SYNTAX INTEGER {
			normal(0),
			alarm(1)
 }
		MAX-ACCESS read-only
		STATUS current
		DESCRIPTION
		"returnairlowhumalarm, status."
		::= { group2 29}
highpressurelockalarm OBJECT-TYPE
		SYNTAX INTEGER {
			normal(0),
			alarm(1)
 }
		MAX-ACCESS read-only
		STATUS current
		DESCRIPTION
		"highpressurelockalarm, status."
		::= { group2 30}
lowpressurelockalarm OBJECT-TYPE
		SYNTAX INTEGER {
			normal(0),
			alarm(1)
 }
		MAX-ACCESS read-only
		STATUS current
		DESCRIPTION
		"lowpressurelockalarm, status."
		::= { group2 31}
lockexhausttemperaturealarm OBJECT-TYPE
		SYNTAX INTEGER {
			normal(0),
			alarm(1)
 }
		MAX-ACCESS read-only
		STATUS current
		DESCRIPTION
		"lockexhausttemperaturealarm, status."
		::= { group2 32}
lowexhaustsuperheatlockalar OBJECT-TYPE
		SYNTAX INTEGER {
			normal(0),
			alarm(1)
 }
		MAX-ACCESS read-only
		STATUS current
		DESCRIPTION
		"lowexhaustsuperheatlockalar, status."
		::= { group2 33}
powerlossalarm OBJECT-TYPE
		SYNTAX INTEGER {
			normal(0),
			alarm(1)
 }
		MAX-ACCESS read-only
		STATUS current
		DESCRIPTION
		"powerlossalarm, status."
		::= { group2 34}
powerovervoltagealarm OBJECT-TYPE
		SYNTAX INTEGER {
			normal(0),
			alarm(1)
 }
		MAX-ACCESS read-only
		STATUS current
		DESCRIPTION
		"powerovervoltagealarm, status."
		::= { group2 35}
powerundervoltagealarm OBJECT-TYPE
		SYNTAX INTEGER {
			normal(0),
			alarm(1)
 }
		MAX-ACCESS read-only
		STATUS current
		DESCRIPTION
		"powerundervoltagealarm, status."
		::= { group2 36}
powerlosephasealarm OBJECT-TYPE
		SYNTAX INTEGER {
			normal(0),
			alarm(1)
 }
		MAX-ACCESS read-only
		STATUS current
		DESCRIPTION
		"powerlosephasealarm, status."
		::= { group2 37}
flooroverflowalarm OBJECT-TYPE
		SYNTAX INTEGER {
			normal(0),
			alarm(1)
 }
		MAX-ACCESS read-only
		STATUS current
		DESCRIPTION
		"flooroverflowalarm, status."
		::= { group2 38}
highwaterlevelalarm OBJECT-TYPE
		SYNTAX INTEGER {
			normal(0),
			alarm(1)
 }
		MAX-ACCESS read-only
		STATUS current
		DESCRIPTION
		"highwaterlevelalarm, status."
		::= { group2 39}
filtercloggedalarm OBJECT-TYPE
		SYNTAX INTEGER {
			normal(0),
			alarm(1)
 }
		MAX-ACCESS read-only
		STATUS current
		DESCRIPTION
		"filtercloggedalarm, status."
		::= { group2 40}
filtermaintenance OBJECT-TYPE
		SYNTAX INTEGER {
			normal(0),
			alarm(1)
 }
		MAX-ACCESS read-only
		STATUS current
		DESCRIPTION
		"filtermaintenance, status."
		::= { group2 41}
airflowlossalarm OBJECT-TYPE
		SYNTAX INTEGER {
			normal(0),
			alarm(1)
 }
		MAX-ACCESS read-only
		STATUS current
		DESCRIPTION
		"airflowlossalarm, status."
		::= { group2 42}
lowpressuresensorlock OBJECT-TYPE
		SYNTAX INTEGER {
			normal(0),
			alarm(1)
 }
		MAX-ACCESS read-only
		STATUS current
		DESCRIPTION
		"lowpressuresensorlock, status."
		::= { group2 43}
remoteshutdownalarm OBJECT-TYPE
		SYNTAX INTEGER {
			normal(0),
			alarm(1)
 }
		MAX-ACCESS read-only
		STATUS current
		DESCRIPTION
		"remoteshutdownalarm, status."
		::= { group2 44}
grouphostlossalarm OBJECT-TYPE
		SYNTAX INTEGER {
			normal(0),
			alarm(1)
 }
		MAX-ACCESS read-only
		STATUS current
		DESCRIPTION
		"grouphostlossalarm, status."
		::= { group2 45}
groupslavelossalarm OBJECT-TYPE
		SYNTAX INTEGER {
			normal(0),
			alarm(1)
 }
		MAX-ACCESS read-only
		STATUS current
		DESCRIPTION
		"groupslavelossalarm, status."
		::= { group2 46}
returnairtempsensorfault OBJECT-TYPE
		SYNTAX INTEGER {
			normal(0),
			alarm(1)
 }
		MAX-ACCESS read-only
		STATUS current
		DESCRIPTION
		"returnairtempsensorfault, status."
		::= { group2 47}
returnairhumsensorfault OBJECT-TYPE
		SYNTAX INTEGER {
			normal(0),
			alarm(1)
 }
		MAX-ACCESS read-only
		STATUS current
		DESCRIPTION
		"returnairhumsensorfault, status."
		::= { group2 48}
supplyairtempdiffsensorfau OBJECT-TYPE
		SYNTAX INTEGER {
			normal(0),
			alarm(1)
 }
		MAX-ACCESS read-only
		STATUS current
		DESCRIPTION
		"supplyairtempdiffsensorfau, status."
		::= { group2 49}
supplyairtempsensorfault OBJECT-TYPE
		SYNTAX INTEGER {
			normal(0),
			alarm(1)
 }
		MAX-ACCESS read-only
		STATUS current
		DESCRIPTION
		"supplyairtempsensorfault, status."
		::= { group2 50}
remotetempsensorfault OBJECT-TYPE
		SYNTAX INTEGER {
			normal(0),
			alarm(1)
 }
		MAX-ACCESS read-only
		STATUS current
		DESCRIPTION
		"remotetempsensorfault, status."
		::= { group2 51}
highpressuresensorfault OBJECT-TYPE
		SYNTAX INTEGER {
			normal(0),
			alarm(1)
 }
		MAX-ACCESS read-only
		STATUS current
		DESCRIPTION
		"highpressuresensorfault, status."
		::= { group2 52}
electricheatingfailurealarm OBJECT-TYPE
		SYNTAX INTEGER {
			normal(0),
			alarm(1)
 }
		MAX-ACCESS read-only
		STATUS current
		DESCRIPTION
		"electricheatingfailurealarm, status."
		::= { group2 53}
exhaustgastempsensorfault OBJECT-TYPE
		SYNTAX INTEGER {
			normal(0),
			alarm(1)
 }
		MAX-ACCESS read-only
		STATUS current
		DESCRIPTION
		"exhaustgastempsensorfault, status."
		::= { group2 54}
fanpowerfailure OBJECT-TYPE
		SYNTAX INTEGER {
			normal(0),
			alarm(1)
 }
		MAX-ACCESS read-only
		STATUS current
		DESCRIPTION
		"fanpowerfailure, status."
		::= { group2 55}
eevcommunicationfailure OBJECT-TYPE
		SYNTAX INTEGER {
			normal(0),
			alarm(1)
 }
		MAX-ACCESS read-only
		STATUS current
		DESCRIPTION
		"eevcommunicationfailure, status."
		::= { group2 56}
notselectedrefrigerantalarm OBJECT-TYPE
		SYNTAX INTEGER {
			normal(0),
			alarm(1)
 }
		MAX-ACCESS read-only
		STATUS current
		DESCRIPTION
		"notselectedrefrigerantalarm, status."
		::= { group2 57}
refrigerantshortagealarm OBJECT-TYPE
		SYNTAX INTEGER {
			normal(0),
			alarm(1)
 }
		MAX-ACCESS read-only
		STATUS current
		DESCRIPTION
		"refrigerantshortagealarm, status."
		::= { group2 58}
intakeairtemperaturesensorf OBJECT-TYPE
		SYNTAX INTEGER {
			normal(0),
			alarm(1)
 }
		MAX-ACCESS read-only
		STATUS current
		DESCRIPTION
		"intakeairtemperaturesensorf, status."
		::= { group2 59}
lowpressuresensorfault OBJECT-TYPE
		SYNTAX INTEGER {
			normal(0),
			alarm(1)
 }
		MAX-ACCESS read-only
		STATUS current
		DESCRIPTION
		"lowpressuresensorfault, status."
		::= { group2 60}
compressordrivecommunication OBJECT-TYPE
		SYNTAX INTEGER {
			normal(0),
			alarm(1)
 }
		MAX-ACCESS read-only
		STATUS current
		DESCRIPTION
		"compressordrivecommunication, status."
		::= { group2 61}
compressordrivefault OBJECT-TYPE
		SYNTAX INTEGER {
			normal(0),
			alarm(1)
 }
		MAX-ACCESS read-only
		STATUS current
		DESCRIPTION
		"compressordrivefault, status."
		::= { group2 62}
compressorradiatorovertemper OBJECT-TYPE
		SYNTAX INTEGER {
			normal(0),
			alarm(1)
 }
		MAX-ACCESS read-only
		STATUS current
		DESCRIPTION
		"compressorradiatorovertemper, status."
		::= { group2 63}
compressorovercurrentprotecti OBJECT-TYPE
		SYNTAX INTEGER {
			normal(0),
			alarm(1)
 }
		MAX-ACCESS read-only
		STATUS current
		DESCRIPTION
		"compressorovercurrentprotecti, status."
		::= { group2 64}
compressorphaselossprotectio OBJECT-TYPE
		SYNTAX INTEGER {
			normal(0),
			alarm(1)
 }
		MAX-ACCESS read-only
		STATUS current
		DESCRIPTION
		"compressorphaselossprotectio, status."
		::= { group2 65}
compressorbusvoltagefault OBJECT-TYPE
		SYNTAX INTEGER {
			normal(0),
			alarm(1)
 }
		MAX-ACCESS read-only
		STATUS current
		DESCRIPTION
		"compressorbusvoltagefault, status."
		::= { group2 66}
humidifierfaultalarm OBJECT-TYPE
		SYNTAX INTEGER {
			normal(0),
			alarm(1)
 }
		MAX-ACCESS read-only
		STATUS current
		DESCRIPTION
		"humidifierfaultalarm, status."
		::= { group2 67}
groupaddressrepeatedalarm OBJECT-TYPE
		SYNTAX INTEGER {
			normal(0),
			alarm(1)
 }
		MAX-ACCESS read-only
		STATUS current
		DESCRIPTION
		"groupaddressrepeatedalarm, status."
		::= { group2 68}
supplyairtemperature OBJECT-TYPE
		SYNTAX Integer32
		
		MAX-ACCESS read-only
		STATUS current
		DESCRIPTION
		"supplyairtemperature, stored as 0.01℃."
		::= { group2 69}
returnairtemperature OBJECT-TYPE
		SYNTAX Integer32
		
		MAX-ACCESS read-only
		STATUS current
		DESCRIPTION
		"returnairtemperature, stored as 0.01℃."
		::= { group2 70}
returnairhumidity OBJECT-TYPE
		SYNTAX Integer32
		
		MAX-ACCESS read-only
		STATUS current
		DESCRIPTION
		"returnairhumidity, stored as 0.01."
		::= { group2 71}
theoreticalairhumidity OBJECT-TYPE
		SYNTAX Integer32
		
		MAX-ACCESS read-only
		STATUS current
		DESCRIPTION
		"theoreticalairhumidity, stored as 0.01."
		::= { group2 72}
aphasevoltage OBJECT-TYPE
		SYNTAX Integer32
		
		MAX-ACCESS read-only
		STATUS current
		DESCRIPTION
		"aphasevoltage, stored as 0.01V."
		::= { group2 73}
bphasevoltage OBJECT-TYPE
		SYNTAX Integer32
		
		MAX-ACCESS read-only
		STATUS current
		DESCRIPTION
		"bphasevoltage, stored as 0.01V."
		::= { group2 74}
cphasevoltage OBJECT-TYPE
		SYNTAX Integer32
		
		MAX-ACCESS read-only
		STATUS current
		DESCRIPTION
		"cphasevoltage, stored as 0.01V."
		::= { group2 75}
powerfrequency OBJECT-TYPE
		SYNTAX Integer32
		
		MAX-ACCESS read-only
		STATUS current
		DESCRIPTION
		"powerfrequency, stored as 0.01Hz."
		::= { group2 76}
unitoperationstatus OBJECT-TYPE
		SYNTAX INTEGER {
			run(0),
			shutdown(1),
			standby(2),
			locking(3)
 }
		MAX-ACCESS read-only
		STATUS current
		DESCRIPTION
		"unitoperationstatus, status."
		::= { group2 77}
unitgroupcontrolmode OBJECT-TYPE
		SYNTAX INTEGER {
			single(0),
			groupcontrol(1)
 }
		MAX-ACCESS read-only
		STATUS current
		DESCRIPTION
		"unitgroupcontrolmode, status."
		::= { group2 78}
compressorcapacity OBJECT-TYPE
		SYNTAX Integer32
		
		MAX-ACCESS read-only
		STATUS current
		DESCRIPTION
		"compressorcapacity, stored as 0.01."
		::= { group2 79}
fanspeed OBJECT-TYPE
		SYNTAX Integer32
		
		MAX-ACCESS read-only
		STATUS current
		DESCRIPTION
		"fanspeed, stored as 0.01."
		::= { group2 80}
communicatestatus OBJECT-TYPE
		SYNTAX INTEGER {
			normal(0),
			alarm(1)
 }
		MAX-ACCESS read-only
		STATUS current
		DESCRIPTION
		"communicatestatus, status."
		::= { group2 81}

------------------------------------------------------------
--gourp3
------------------------------------------------------------
group3 OBJECT IDENTIFIER ::= { system 3 }
remoteon OBJECT-TYPE
		SYNTAX INTEGER {
			run(0)
 }
		MAX-ACCESS read-write
		STATUS current
		DESCRIPTION
		"remoteon, status."
		::= { group3 82}
remoteoff OBJECT-TYPE
		SYNTAX INTEGER {
			shutdown(0)
 }
		MAX-ACCESS read-write
		STATUS current
		DESCRIPTION
		"remoteoff, status."
		::= { group3 83}

------------------------------------------------------------
--gourp4
------------------------------------------------------------
group4 OBJECT IDENTIFIER ::= { system 4 }
supplyairtemperaturesetpoint OBJECT-TYPE
		SYNTAX Integer32
		
		MAX-ACCESS read-write
		STATUS current
		DESCRIPTION
		"supplyairtemperaturesetpoint, stored as 1℃."
		::= { group4 84}
remotetemperaturesetpoint OBJECT-TYPE
		SYNTAX Integer32
		
		MAX-ACCESS read-write
		STATUS current
		DESCRIPTION
		"remotetemperaturesetpoint, stored as 1℃."
		::= { group4 85}
returnairtemperaturesetpoin OBJECT-TYPE
		SYNTAX Integer32
		
		MAX-ACCESS read-write
		STATUS current
		DESCRIPTION
		"returnairtemperaturesetpoin, stored as 1℃."
		::= { group4 86}
supplyairhumiditysetpoint OBJECT-TYPE
		SYNTAX Integer32
		
		MAX-ACCESS read-write
		STATUS current
		DESCRIPTION
		"supplyairhumiditysetpoint, stored as 1."
		::= { group4 87}
lognumberset OBJECT-TYPE
		SYNTAX Integer32
		
		MAX-ACCESS read-write
		STATUS current
		DESCRIPTION
		"lognumberset, stored as 1."
		::= { group4 88}
------------------------------------------------------------
-- 3 Alarm trap table 
-- If you want to know the equipment trap list detail,
-- Please find a Excel file named "RDU-SIC G2 trap table";
------------------------------------------------------------

alarmTrapTable OBJECT-TYPE
	SYNTAX SEQUENCE OF AlarmTrapEntry
	MAX-ACCESS not-accessible
	STATUS current
	DESCRIPTION "
		Table holding information about the submitted alarm traps."
	::= { ENP_AC_CRV+  3 }

alarmTrapEntry OBJECT-TYPE
	SYNTAX AlarmTrapEntry
	MAX-ACCESS not-accessible
	STATUS current
	DESCRIPTION "
		An entry (conceptual row) in the alarmTrapTable."
	INDEX { alarmIndex }
	::= { alarmTrapTable 1 }

AlarmTrapEntry ::= SEQUENCE {
	alarmIndex Counter32,
	alarmTime DisplayString,
	alarmStatusChange StatusChange,
	alarmSeverity Status,
	alarmDescription DisplayString,
	alarmId Integer32 }

alarmIndex OBJECT-TYPE
	SYNTAX Counter32
	MAX-ACCESS read-only
	STATUS current
	DESCRIPTION "
		The unique sequence number of this alarm trap."
	::= { alarmTrapEntry 1 }

alarmTime OBJECT-TYPE
	SYNTAX DisplayString
	MAX-ACCESS read-only
	STATUS current
	DESCRIPTION "
		Date and time when event occured."
	::= { alarmTrapEntry 2 }

alarmStatusChange OBJECT-TYPE
	SYNTAX StatusChange
	MAX-ACCESS read-only
	STATUS current
	DESCRIPTION "
		Indicates 'activated' (0) or 'deactivated' (1) alarm events."
	::= { alarmTrapEntry 3 }

alarmSeverity OBJECT-TYPE
	SYNTAX Status
	MAX-ACCESS read-only
	STATUS current
	DESCRIPTION "
		The severity of the alarm. One of
		(0) informational
		(1) warning
		(2) critical"
	::= { alarmTrapEntry 4 }
	
alarmDescription OBJECT-TYPE
	SYNTAX DisplayString
	MAX-ACCESS read-only
	STATUS current
	DESCRIPTION "
		Free-text description of alarm."
	::= { alarmTrapEntry 5 }
	
alarmId OBJECT-TYPE
	SYNTAX Integer32
	MAX-ACCESS read-only
	STATUS current
	DESCRIPTION "
		Alarm Index in system."
	::= { alarmTrapEntry 6 }

	
	
------------------------------------------------------------
-- System Alarm Trap Define
------------------------------------------------------------

systemAlarmTrap OBJECT IDENTIFIER ::= { ENP_AC_CRV+ 4 }

systemAlarmTrapFormatDefine NOTIFICATION-TYPE
	OBJECTS {
		systemAlarmIndex,
		systemAlarmTime,
		systemAlarmStatusChange,
		systemAlarmSeverity,
		systemAlarmDescription,
		systemAlarmId,
		systemAlarmEquipId,
		systemAlarmEquipTypeId }
	STATUS current
	DESCRIPTION "
		An alarm trap is sent when an alarm occurs (activated) or
		returns to normal state (deactivated). Alarm traps are logged
		in alarmTrapTable. Variables in this trap:
		* systemAlarmIndex - The unique sequence number of this alarm trap.
		* systemAlarmTime - Date and time when event occured (local time).
		* systemAlarmStatusChange - (0) activated or (1) deactivated.
		* systemAlarmSeverity - The severity of the alarm..
		* systemAlarmId - Alarm id.
		* systemAlarmEquipId - Alarm equipment id.
		* systemAlarmEquipTypeId - Alarm equipment type id."
	::= { systemAlarmTrap 1 }
	
	
------------------------------------------------------------
-- End of MIB definitions
------------------------------------------------------------
END
